module example-deviation-b {
  yang-version 1.1;
  namespace "urn:example:deviations";
  prefix "ex-dev";

  // Import the original module to reference its paths
  import example-config {
    prefix "ex";
  }

  organization "Data Architect Solutions";
  description "Deviations to prune top-con structure.";

  revision 2026-02-26 {
    description "Removed con-b and attr-2.";
  }

  // Deviation to remove the 'con-b' container and its child 'attr-b-1'
  deviation "/ex:top-con/ex:con-b" {
    description "Removing con-b and its nested child attr-b-1.";
    deviate not-supported;
  }

  // Deviation to remove the 'attr-2' leaf
  deviation "/ex:top-con/ex:attr-2" {
    description "Removing the attr-2 leaf from top-con.";
    deviate not-supported;
  }
}
